KKDCP { }

DEFINITIONS EXPLICIT TAGS ::=

BEGIN

KDC-PROXY-MESSAGE ::= SEQUENCE {
  kerb-message [0] OCTET STRING,
  target-domain [1] GeneralString OPTIONAL,
  dclocator-hint [2] INTEGER OPTIONAL
}

END
